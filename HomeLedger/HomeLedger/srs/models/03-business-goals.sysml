package HomeLedgerBusinessGoals {
    // Бизнес-цели Заказчика; каждое требование SRS ссылается на одну из них

    requirement <BG> 'Бизнес-цели HomeLedger' {
        requirement <BG1> 'БЦ-1 Полный учёт денег' {
            doc /* Записывать все доходы и расходы в одном месте
                 * вместо заметок в телефоне и памяти. */
        }
        requirement <BG2> 'БЦ-2 Понятная структура трат' {
            doc /* Видеть, на какие категории уходят деньги
                 * и как траты меняются по месяцам. */
        }
        requirement <BG3> 'БЦ-3 Контроль бюджета' {
            doc /* Не превышать месячные лимиты по категориям;
                 * узнавать о приближении к лимиту сразу. */
        }
        requirement <BG4> 'БЦ-4 Регулярные накопления' {
            doc /* Откладывать не менее 20 % дохода
                 * с помощью конкретных советов по тратам. */
        }
        requirement <BG5> 'БЦ-5 Быстрый ввод' {
            doc /* Вносить операцию не дольше 15 секунд,
                 * чтобы учёт не был заброшен. */
        }
    }
}
