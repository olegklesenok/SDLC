package HomeLedgerUseCases {
    // Варианты использования ПО HomeLedger
    private import HomeLedgerContext::*;

    use case def <UC1> 'ВИ-1 Внести расход или доход' {
        subject 'ПО HomeLedger' : 'Программное средство';
        actor 'Владелец бюджета' : 'Пользователь';
        actor 'Член семьи' : 'Пользователь';
    }
    use case def <UC2> 'ВИ-2 Перевести между кошельками' {
        subject 'ПО HomeLedger' : 'Программное средство';
        actor 'Владелец бюджета' : 'Пользователь';
    }
    use case def <UC3> 'ВИ-3 Просмотреть и исправить журнал' {
        subject 'ПО HomeLedger' : 'Программное средство';
        actor 'Владелец бюджета' : 'Пользователь';
        actor 'Член семьи' : 'Пользователь';
    }
    use case def <UC4> 'ВИ-4 Посмотреть баланс и статистику' {
        subject 'ПО HomeLedger' : 'Программное средство';
        actor 'Владелец бюджета' : 'Пользователь';
        actor 'Член семьи' : 'Пользователь';
    }
    use case def <UC5> 'ВИ-5 Установить лимиты по категориям' {
        subject 'ПО HomeLedger' : 'Программное средство';
        actor 'Владелец бюджета' : 'Пользователь';
    }
    use case def <UC6> 'ВИ-6 Получить советы по организации трат' {
        subject 'ПО HomeLedger' : 'Программное средство';
        actor 'Владелец бюджета' : 'Пользователь';
    }
    use case def <UC7> 'ВИ-7 Настроить кошельки и категории' {
        subject 'ПО HomeLedger' : 'Программное средство';
        actor 'Владелец бюджета' : 'Пользователь';
    }
    use case def <UC8> 'ВИ-8 Экспортировать отчёт за месяц' {
        subject 'ПО HomeLedger' : 'Программное средство';
        actor 'Владелец бюджета' : 'Пользователь';
    }
}
